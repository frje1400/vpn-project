module layer3vpn {
    namespace "http://lundnet.com/ns/yang/layer3vpn";
    prefix "vpn";

    organization "LundNet AB.";
    
    contact
        "Fredrik Jeppsson
        email: frje1400@student.miun.se";

    description
        "Yang module for L3VPN written by Fredrik Jeppsson.";

    revision 2017-05-25 {
        description "version 1.0";
    }

    container layer3vpn {
        container general {
            leaf description {
                type string;
                description "Optional description string, e.g. for customer info.";
            }
            leaf vpn-id {
                type vpn-id;
                mandatory true;
                description "Customer VPN ID from 1 to 255.";
            }
            leaf management-rt {
                type route-target;
                mandatory true;
                description "Route target for import to management vrf.";
            }
            leaf management-ip {
                type ipv4-prefix;
                mandatory true;
                description "IP of management station.";
            }
        }
        container routers {
            list router {
                key router-name;
                leaf router-name {
                    type string;
                    mandatory true;
                    description "Name of router.";
                }
                container interfaces {
                    list interface {
                        key int-name;
                        leaf int-name {
                            type string;
                            mandatory true;
                            description "interface name - case sensitive.";
                        }
                        leaf address {
                            type ipv4-prefix;
                            mandatory true;
                            description "interface IPv4 address in x.x.x.x/y notation.";
                        }
                        leaf bandwidth {
                            type bandwidth;
                            description "interface policer bandwidth.";
                        }
                    }
                }
                container routing {
                    container static {
                        list route {
                            key network;
                            leaf network {
                                type ipv4-prefix;
                                mandatory true;
                                description "IPv4 prefix for static route.";
                            }
                            leaf next-hop {
                                type ipv4-address;
                                mandatory true;
                                description "IPv4 static route next hop.";
                            }
                        }
                    }
                    container bgp {
                        list neighbor {
                            key address;
                            leaf address {
                                type ipv4-address;
                                mandatory true;
                                description "IPv4 address of BGP neighbor.";
                            }
                            leaf remote-as {
                                type uint32;
                                mandatory true;
                                description "BGP ASN of neighbor.";
                            }
                        }
                    }
                }
            }
        } 
    }


    // custom types.

    typedef vpn-id {
        type uint32 {
            range "1 .. 255";
        }
        description 
            "Customer vpn id must be between 1 and 255.";
    }

    typedef bandwidth {
        type uint32 {
            range "100 | 200 | 500";
        }
        description
            "Allowed bandwidth levels are 100 Mbps, 200 Mbps, 500 Mbps.";
    }

    typedef route-target {
        type string {
            pattern
                "100:[0-9]{3}";
        }
        description
            "Pattern for ensuring that route target follows format 100:xxx.
             Matches 100: followed by any three digit number, e.g. 100:999";
    }


     
    /*  IPv4 address types from RFC 6991  
        https://tools.ietf.org/html/rfc6991
        "This document introduces a collection of 
        common data types to be used with the YANG
        data modeling language."
    */

    typedef ipv4-prefix {
        type string {
            pattern
                '(([0-9]|[1-9][0-9]|1[0-9][0-9]|2[0-4][0-9]|25[0-5])\.){3}'
            +  '([0-9]|[1-9][0-9]|1[0-9][0-9]|2[0-4][0-9]|25[0-5])'
            + '/(([0-9])|([1-2][0-9])|(3[0-2]))';
        }
        description
        "The ipv4-prefix type represents an IPv4 address prefix.
         The prefix length is given by the number following the
         slash character and must be less than or equal to 32.

         A prefix length value of n corresponds to an IP address
         mask that has n contiguous 1-bits from the most
         significant bit (MSB) and all other bits set to 0.

         The canonical format of an IPv4 prefix has all bits of
         the IPv4 address set to zero that are not part of the
         IPv4 prefix.";
    }

    typedef ipv4-address {
        type string {
            pattern
                '(([0-9]|[1-9][0-9]|1[0-9][0-9]|2[0-4][0-9]|25[0-5])\.){3}'
            +  '([0-9]|[1-9][0-9]|1[0-9][0-9]|2[0-4][0-9]|25[0-5])'
            + '(%[\p{N}\p{L}]+)?';
        }
        description
         "The ipv4-address type represents an IPv4 address in
          dotted-quad notation.  The IPv4 address may include a zone
          index, separated by a % sign.

          The zone index is used to disambiguate identical address
          values.  For link-local addresses, the zone index will
          typically be the interface index number or the name of an
          interface.  If the zone index is not present, the default
          zone of the device will be used.

          The canonical format for the zone index is the numerical
          format";
    }
}
